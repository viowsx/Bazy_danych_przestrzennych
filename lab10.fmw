FME workspace lab10.fmw
Startup Python:
      import fme
      import smtplib
      from email.mime.text import MIMEText
      from email.mime.multipart import MIMEMultipart
      from datetime import datetime

      # Message variables
      curDate = datetime.now().strftime("%d.%m.%Y")
      curTime = datetime.now().strftime("%H:%M:%S")
      powiat = FME_MacroValues['powiat']

      # Email configuration
      sender_email = FME_MacroValues['e-mail_sender']
      receiver_email = FME_MacroValues['e-mail_klienta']
      subject = "FME Startup State"
      body = 'Drogi użytkowniku ' + receiver_email + ', dnia ' + curDate + ' o godzinie ' + curTime + ' rozpoczęto przetwarzanie danych dla powiatu ' + powiat + '.'

      # SMTP server configuration
      smtp_server = "smtp.gmail.com"
      smtp_port = 587
      smtp_username = FME_MacroValues['e-mail_sender']
      smtp_password = FME_MacroValues['pass_sender']

      # Create a MIME object
      message = MIMEMultipart()
      message["From"] = sender_email
      message["To"] = receiver_email
      message["Subject"] = subject

      # Attach the body to the message
      message.attach(MIMEText(body, "plain"))

      # Connect to the SMTP server
      with smtplib.SMTP(smtp_server, smtp_port) as server:
          # Start the TLS connection
          server.starttls()

          # Log in to the email account
          server.login(smtp_username, smtp_password)

          # Send the email
          server.sendmail(sender_email, receiver_email, message.as_string())

      print("Email sent successfully!")

Parameters:
- API =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   # Enter API Key
- e-mail_klienta = wchudzinska1@gmail.com   # Enter client email
- powiat = Świnoujście   # Enter name of the county
- cloud_coverage = 50   # Enter cloud coverage
- date_start = 20230701   # Enter a Start Date
- date_finish = 20230730   # Enter a Finish Date
- e-mail_sender = wchudzinska1@gmail.com   # Enter Text Data
- SourceDataset_SHAPEFILE = $(FME_MF_DIR)powiaty.shp   # Source Esri Shapefile(s)
- DestDataset_TIFF = C:\Users\wchud\Desktop\studia\3_rok\bazy\cwiczenia10   # Destination TIFF (Tagged Image File Format) Folder
- pass_sender =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   # Enter a Password

Readers:
- SHAPEFILE_1: SHAPEFILE from $(SourceDataset_SHAPEFILE)

Writers:
- TIFF_1: TIFF to $(DestDataset_TIFF)

powiaty (reader SHAPEFILE_1)
    attributes: gml_id varchar(254), JPT_SJR_KO varchar(254), JPT_POWIER varchar(254), JPT_KOD_JE varchar(254), JPT_NAZWA_ varchar(254), JPT_ORGAN_ varchar(254), JPT_JOR_ID varchar(254), WERSJA_OD varchar(254), WERSJA_DO varchar(254), WAZNY_OD varchar(254), WAZNY_DO varchar(254), JPT_KOD__1 varchar(254), JPT_NAZWA1 varchar(254), JPT_ORGAN1 varchar(254), JPT_WAZNA_ varchar(254), ID_BUFORA_ varchar(254), ID_BUFORA1 varchar(254), ID_TECHNIC varchar(254), IIP_PRZEST varchar(254), IIP_IDENTY varchar(254), IIP_WERSJA varchar(254), JPT_KJ_IIP varchar(254), JPT_KJ_I_1 varchar(254), JPT_KJ_I_2 varchar(254), JPT_OPIS varchar(254), JPT_SPS_KO varchar(254), ID_BUFOR_1 varchar(254), JPT_ID varchar(254), JPT_POWI_1 varchar(254), JPT_KJ_I_3 varchar(254),
      JPT_GEOMET varchar(254), JPT_GEOM_1 varchar(254), SHAPE_LENG varchar(254), SHAPE_AREA varchar(254), REGON varchar(254), RODZAJ varchar(254)
    -> TestFilter
TestFilter
    DEFAULT_VALUE = <UNFILTERED>
    PASSED_TEST_GROUP_OUTPUT = FIRST
    TEST_LIST = "BOOL_OP,OR,COMPOSITE_TEST,""""""1"""""",TEST_CLAUSE,TEST @Value(JPT_NAZWA_) = powiat $(powiat)",@Value(JPT_NAZWA_) = powiat __powiat_
    @Value(JPT_NAZWA_) = powiat __powiat_ -> Inspector_2
    @Value(JPT_NAZWA_) = powiat __powiat_ -> Reprojector
Reprojector
    DEST = EPSG:4326
    INTERPOLATION_TYPE_NAME = Nearest Neighbor
    RASTER_CELL_SIZE = Preserve Cells
    RASTER_TOLERANCE = 0.0
    REPROJECTED -> Clipper [CLIPPER]
    REPROJECTED -> BoundingBoxAccumulator
BoundingBoxAccumulator
    ACCUM_ATTRS_NAME = Use Attributes From One Feature
    BOUNDING_BOX -> EarthCacheConnector
EarthCacheConnector
    api_key =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
    end_date = $(date_finish)
    interval = 7
    min_aoi_coverage_percentage = $(cloud_coverage)
    output_id = rgbn-a3e8-11e7-9793-ae4260ee3b4b
    pipeline_name = sentinel$(powiat)
    start_date = $(date_start)
    -> Sampler
    <Rejected> -> Terminator
Sampler
    RATE = 1
    SAMPLE_MODE = No
    SAMPLE_TYPE_LONG = Last N Features
    SAMPLED -> RasterBandSeparator
    SAMPLED -> Inspector_4
RasterBandSeparator
    BAND_INDEX_FIELD = _band_index
    PALETTE_INDEX_FIELD = _palette_index
    RASTER_INDEX_FIELD = _raster_index
    SPLIT_BY_NAME = Band and Palette
    -> TestFilter_RED
    -> TestFilter_NIR
TestFilter_RED
    DEFAULT_VALUE = <UNFILTERED>
    PASSED_TEST_GROUP_OUTPUT = FIRST
    TEST_LIST = "BOOL_OP,OR,COMPOSITE_TEST,""""""1"""""",TEST_CLAUSE,TEST @Value(_band_index) = 0",@Value(_band_index) = 0
    @Value(_band_index) = 0 -> NDVICalculator [Red]
TestFilter_NIR
    DEFAULT_VALUE = <UNFILTERED>
    PASSED_TEST_GROUP_OUTPUT = FIRST
    TEST_LIST = "BOOL_OP,OR,COMPOSITE_TEST,""""""1"""""",TEST_CLAUSE,TEST @Value(_band_index) = 3",@Value(_band_index) = 3
    @Value(_band_index) = 3 -> NDVICalculator [Infrared]
NDVICalculator
    COLORIZE = Blue-Yellow-Green Palette
    INDEXTYPE = NDVI
    SAVIADJUSTMENT = 0.5
    -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> RasterStatisticsCalculator
    INSIDE -> powiaty (writer TIFF_1)
powiaty (writer TIFF_1)
    attributes: gml_id char(254), JPT_SJR_KO char(254), JPT_POWIER char(254), JPT_KOD_JE char(254), JPT_NAZWA_ char(254), JPT_ORGAN_ char(254), JPT_JOR_ID char(254), WERSJA_OD char(254), WERSJA_DO char(254), WAZNY_OD char(254), WAZNY_DO char(254), JPT_KOD__1 char(254), JPT_NAZWA1 char(254), JPT_ORGAN1 char(254), JPT_WAZNA_ char(254), ID_BUFORA_ char(254), ID_BUFORA1 char(254), ID_TECHNIC char(254), IIP_PRZEST char(254), IIP_IDENTY char(254), IIP_WERSJA char(254), JPT_KJ_IIP char(254), JPT_KJ_I_1 char(254), JPT_KJ_I_2 char(254), JPT_OPIS char(254), JPT_SPS_KO char(254), ID_BUFOR_1 char(254), JPT_ID char(254), JPT_POWI_1 char(254), JPT_KJ_I_3 char(254),
      JPT_GEOMET char(254), JPT_GEOM_1 char(254), SHAPE_LENG char(254), SHAPE_AREA char(254), REGON char(254), RODZAJ char(254)
RasterStatisticsCalculator
    RASTER_LEVEL = BAND_ONLY
    RASTER_STATS = "0   MEAN   STDEV   "
    -> Inspector
    -> PythonCaller
Inspector
PythonCaller
    PYTHONSOURCE:
      import fme
      import fmeobjects


      class FeatureProcessor(object):
          """Template Class Interface:
          When using this class, make sure its name is set as the value of the 'Class to Process Features'
          transformer parameter.
          """

          def __init__(self):
              """Base constructor for class members."""
              pass

          def has_support_for(self, support_type: int):
              """This method is called by FME to determine if the PythonCaller supports Bulk mode,
              which allows for significant performance gains when processing large numbers of features.
              Bulk mode cannot always be supported.
              More information available in transformer help.
              """
              return support_type == fmeobjects.FME_SUPPORT_FEATURE_TABLE_SHIM

          def input(self, feature: fmeobjects.FMEFeature):
              """This method is called for each feature which enters the PythonCaller.
              Processed input features can be emitted from this method using self.pyoutput().
              If knowledge of all input features is required for processing, then input features should be
              cached to a list instance variable and processed using group processing or in the close() method.
              """
              self.pyoutput(feature)

          def close(self):
              """This method is called once all the FME Features have been processed from input()."""
              pass

          def process_group(self):
              """This method is called by FME for each group when group processing mode is enabled.
              This implementation should reset any instance variables used for the next group.
              Bulk mode should not be enabled when using group processing.
              More information available in transformer help.
              """
              pass

      import fme
      import smtplib
      from email.mime.text import MIMEText
      from email.mime.multipart import MIMEMultipart
      from datetime import datetime

      # Message variables
      curDate = datetime.now().strftime("%d.%m.%Y")
      curTime = datetime.now().strftime("%H:%M:%S")
      powiat = FME_MacroValues['powiat']

      # Email configuration
      sender_email = FME_MacroValues['e-mail_sender']
      receiver_email = FME_MacroValues['e-mail_klienta']
      subject = "FME End State"
      body = 'Drogi użytkowniku ' + receiver_email + ', dnia ' + curDate + ' o godzinie ' + curTime + ' pomyślnie zakończono przetwarzanie danych dla powiatu ' + powiat + '.'

      # SMTP server configuration
      smtp_server = "smtp.gmail.com"
      smtp_port = 587
      smtp_username = FME_MacroValues['e-mail_sender']
      smtp_password = FME_MacroValues['pass_sender']

      # Create a MIME object
      message = MIMEMultipart()
      message["From"] = sender_email
      message["To"] = receiver_email
      message["Subject"] = subject

      # Attach the body to the message
      message.attach(MIMEText(body, "plain"))

      # Connect to the SMTP server
      with smtplib.SMTP(smtp_server, smtp_port) as server:
          # Start the TLS connection
          server.starttls()

          # Log in to the email account
          server.login(smtp_username, smtp_password)

          # Send the email
          server.sendmail(sender_email, receiver_email, message.as_string())

      print("Email sent successfully!")
    PYTHONSYMBOL = FeatureProcessor
Inspector_4
Terminator
    MESSAGE = Translation Terminated
Inspector_2
